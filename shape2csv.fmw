FME workspace shape2csv.fmw

Parameters:
- SourceDataset_SHAPE = C:\Users\amiller\Dropbox\Campus Wide As-builts\HotSpots.shp   # Source ESRI Shape File(s)
- DestDataset_CSV = C:\Users\amiller\Dropbox\Campus Wide As-builts   # Destination Comma Separated Value (CSV) Directory

Readers:
- SHAPE_1: SHAPE from $(SourceDataset_SHAPE)

Writers:
- CSV_1: CSV to $(DestDataset_CSV)

HotSpots (reader SHAPE_1)
    attributes: OID_ number(9,0), Name char(60), Shape_Leng number(19,11), Shape_Area number(19,11)
    -> Offsetter
Offsetter
    ZOFF = 0
    YOFF = 5487
    XOFF = 0
    OFFSET -> GeometryExtractor
GeometryExtractor
    OGCVERSION = 1.1
    KIND_LONG = OGC Well Known Text
    ATTR = _geometry
    -> HotSpots (writer CSV_1)
HotSpots (writer CSV_1)
    attributes: GEOM char(255)
